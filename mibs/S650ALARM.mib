--
-- S650ALARM.my
-- MIB generated by MG-SOFT Visual MIB Builder 2013 (64-bit) Version 9.0  Build 760
-- Wednesday, July 26, 2017 at 20:12:56
-- Monday, February 09, 2015 at 15:46:59
--

--  S650ALARM.my
-- Monday, February 09, 2015 at 15:46:59
-- 
--   

	S650ALARM DEFINITIONS ::= BEGIN
 
		IMPORTS
			entPhysicalIndex			
				FROM ENTITY-MIB			
			ifNumber, ifIndex			
				FROM IF-MIB			
			OBJECT-GROUP, MODULE-COMPLIANCE, NOTIFICATION-GROUP			
				FROM SNMPv2-CONF			
			snmpModules, IpAddress, Unsigned32, OBJECT-TYPE, MODULE-IDENTITY, 
			OBJECT-IDENTITY, NOTIFICATION-TYPE			
				FROM SNMPv2-SMI			
			DisplayString, TEXTUAL-CONVENTION			
				FROM SNMPv2-TC			
			symmDeviceDependent			
				FROM SYMM-COMMON-SMI;
	
--    
		-- 1.3.6.1.4.1.9070.1.2.5.7.4
		s650Alarm MODULE-IDENTITY 
			LAST-UPDATED "201903210643Z"		-- March 20, 2019 at 06:43 GMT
			ORGANIZATION 
				"Microsemi"
			CONTACT-INFO 
				"Microsemi Technical Support
				1-888-367-7966 toll free USA
				1-408-428-7907 worldwide
				FTD.support@microsemi.com
				"
			DESCRIPTION 
				"This MIB is the equipment-specific alarm MIB for the SyncServer S650 system.
				"
			REVISION "201903210643Z"		-- March 20, 2019 at 06:43 GMT
			DESCRIPTION 
				"Alarm table for release 1.1"
			::= { symmDeviceDependent 4 }
	
--
-- Type definitions
--
	
		ALARMLEVELTYPE ::= INTEGER
			{
			clear(0),
			critical(2),
			major(3),
			minor(4),
			event(5)
			}

		S650TRANSIENT ::= INTEGER
			{
			stateEvent(0),
			transientEvent(1)
			}

		TrapVer ::= INTEGER
			{
			v2c(1),
			v3(2)
			}

		EnaValue ::= INTEGER
			{
			enable(1),
			disable(2)
			}

		ActionApply ::= INTEGER
			{
			apply(1),
			nonapply(2)
			}

		ImageActive ::= INTEGER
			{
			image1(1),
			image2(2),
			nonpresent(3)
			}

		UserAccessLevel ::= INTEGER
			{
			user(1),
			config(2),
			admin(3)
			}

		UserType ::= INTEGER
			{
			snmpnoauth(1),
			snmpmd5(2),
			snmpsha(3),
			snmpmd5des(4),
			snmpmd5aes(5),
			snmpshades(6),
			snmpshaaes(7)
			}

		Snmpv2AccessLevel ::= INTEGER
			{
			read(1),
			readwrite(2)
			}

		ALARMACTION ::= INTEGER
			{
			clearAlarm(0),
			setAlarm(1),
			transientEvent(2)
			}

	
--
-- Textual conventions
-- 
		DateAndTime ::= TEXTUAL-CONVENTION
			DISPLAY-HINT 
				"2d-1d-1d,1d:1d:1d.1d,1a1d:1d"
			STATUS current
			DESCRIPTION 
				"A date-time specification.
				
				field  octets  contents                  range
				-----  ------  --------                  -----
				  1      1-2   year*                     0..65536
				  2       3    month                     1..12
				  3       4    day                       1..31
				  4       5    hour                      0..23
				  5       6    minutes                   0..59
				  6       7    seconds                   0..60
				               (use 60 for leap-second)
				  7       8    deci-seconds              0..9
				  8       9    direction from UTC        '+' / '-'
				  9      10    hours from UTC*           0..13
				 10      11    minutes from UTC          0..59
				
				* Notes:
				- the value of year is in network-byte order
				- daylight saving time in New Zealand is +13
				
				For example, Tuesday May 26, 1992 at 1:30:15 PM EDT would be
				displayed as:
				
				                 1992-5-26,13:30:15.0,-4:0
				
				
				Note that if only local time is known, then timezone
				information (fields 8-10) is not present."
			SYNTAX OCTET STRING (SIZE (8 | 11))

		S650LatAndLon ::= TEXTUAL-CONVENTION
			DISPLAY-HINT 
				"1a1d:1d:1d.1d"
			STATUS current
			DESCRIPTION 
				"antenna latitude and longitude specification.
				
				field  octets  contents                  range
				-----  ------  --------                  -----
				  1       1    +/-180 deg				 '+' / '-'
				  2       2    degree                    0..180
				  3       3    minute                    0..59
				  4       4    second                    0..59
				  5       5    second fraction           0..99
				
				+/- dd:mm:ss.ss
				
				"
			SYNTAX OCTET STRING (SIZE (5))

		S650AntHeight ::= TEXTUAL-CONVENTION
			DISPLAY-HINT 
				"1a2d.1d"
			STATUS current
			DESCRIPTION 
				"antenna height specification.
				
				field  octets  contents                  range
				-----  ------  --------                  -----
				  1       1    +/-						 '+' / '-'
				  2      2-3   meter                     0..10000
				  3       4    meter fraction            0..99
				
				+/- hh.hh
				
				"
			SYNTAX OCTET STRING (SIZE (4))

		S650LocalTimeOffset ::= TEXTUAL-CONVENTION
			DISPLAY-HINT 
				"1a1d:1d"
			STATUS current
			DESCRIPTION 
				"A local time offset specification.
				
				field  octets  contents                  range
				-----  ------  --------                  -----
				  1       1    direction from UTC        '+' / '-'
				  2       2    hours from UTC*           0..13
				  3       3    minutes from UTC          0..59
				
				* Notes:
				- the value of year is in network-byte order
				- The hours range is 0..13
				
				For example, the -6 local time offset would be
				displayed as:  -6:0
				"
			SYNTAX OCTET STRING (SIZE (3))

		S650Ssm ::= TEXTUAL-CONVENTION
			DISPLAY-HINT 
				"x"
			STATUS current
			DESCRIPTION 
				"The ssm hex code"
			SYNTAX INTEGER (0..255)

	
--
-- Node definitions
--
	
--    This sub-tree will include all alarm, event and client traps of SyncServer S650
-- 
		-- 1.3.6.1.4.1.9070.1.2.5.7.4.1
		s650AlarmNotification OBJECT IDENTIFIER ::= { s650Alarm 1 }

		
--      The notification element definitions
-- 
		-- 1.3.6.1.4.1.9070.1.2.5.7.4.1.1
		s650NotifyElements OBJECT IDENTIFIER ::= { s650AlarmNotification 1 }

		
--      
		-- 1.3.6.1.4.1.9070.1.2.5.7.4.1.1.1
		s650NotifyAlarmEventID OBJECT-TYPE
			SYNTAX Unsigned32
			MAX-ACCESS read-only
			STATUS current
			DESCRIPTION
				"The alarm or event ID of the notification."
			::= { s650NotifyElements 1 }

		
--  
		-- 1.3.6.1.4.1.9070.1.2.5.7.4.1.1.2
		s650NotifyIndex OBJECT-TYPE
			SYNTAX Unsigned32
			MAX-ACCESS read-only
			STATUS current
			DESCRIPTION
				"Internal alarm index for a notification."
			::= { s650NotifyElements 2 }

		
--  
		-- 1.3.6.1.4.1.9070.1.2.5.7.4.1.1.3
		s650NotifySeverity OBJECT-TYPE
			SYNTAX ALARMLEVELTYPE
			MAX-ACCESS read-only
			STATUS current
			DESCRIPTION
				"Alarm severity:
				0 - clear alarm or event
				2 - critical alarm (set, if non-transient)
				3 - major alarm (set, if non-transient)
				4 - minor alarm (set, if non-transient)
				5 - report event (set, if non-transient)
				"
			::= { s650NotifyElements 3 }

--		
		-- 1.3.6.1.4.1.9070.1.2.5.7.4.1.1.4
		s650NotifyTransient OBJECT-TYPE
			SYNTAX S650TRANSIENT
			MAX-ACCESS read-only
			STATUS current
			DESCRIPTION
				"The transient state of an alarm or event. 
				It is either a state event (non-transient) or a transient event (transient)."
			::= { s650NotifyElements 4 }

		
--  
		-- 1.3.6.1.4.1.9070.1.2.5.7.4.1.1.5
		s650NotifyDateTime OBJECT-TYPE
			SYNTAX DisplayString
			MAX-ACCESS read-only
			STATUS current
			DESCRIPTION
				"Date and time of the notification."
			DEFVAL { "" }
			::= { s650NotifyElements 5 }

		
--  
		-- 1.3.6.1.4.1.9070.1.2.5.7.4.1.1.6
		s650NotifyDescription OBJECT-TYPE
			SYNTAX DisplayString
			MAX-ACCESS read-only
			STATUS current
			DESCRIPTION
				"Description of this alarm or event 
				(from the SyncServer S650 internal alarm/event definition table)."
			DEFVAL { "" }
			::= { s650NotifyElements 6 }

		
--
        -- 1.3.6.1.4.1.9070.1.2.5.7.4.1.1.7
		s650NotifyClientAddr OBJECT-TYPE
			SYNTAX IpAddress
			MAX-ACCESS read-only
			STATUS current
			DESCRIPTION
				"The IPv4 address of PTP client that generated the notification."
			::= { s650NotifyElements 7 }

		
--
        -- 1.3.6.1.4.1.9070.1.2.5.7.4.1.1.8
		s650NotifySequenceNum OBJECT-TYPE
			SYNTAX Unsigned32
			MAX-ACCESS read-only
			STATUS current
			DESCRIPTION
				"The sequence number of a notification.  Each notification OID 
				has an independently incrementing sequence number.  These are
                reset when the system is rebooted."
			::= { s650NotifyElements 8 }
		

--  
		-- 1.3.6.1.4.1.9070.1.2.5.7.4.1.1.9
		s650NotifyClientClockID OBJECT-TYPE
			SYNTAX DisplayString
			MAX-ACCESS read-only
			STATUS current
			DESCRIPTION
				"Clock ID of the PTP client that generated the notification."
			::= { s650NotifyElements 9 }


--
		-- 1.3.6.1.4.1.9070.1.2.5.7.4.1.1.10
		s650NotifyAlarmAction OBJECT-TYPE
			SYNTAX ALARMACTION
			MAX-ACCESS read-only
			STATUS current
			DESCRIPTION
				"Description."
			::= { s650NotifyElements 10 }

		
--
        -- 1.3.6.1.4.1.9070.1.2.5.7.4.1.2
		s650AlarmContain OBJECT IDENTIFIER ::= { s650AlarmNotification 2 }

		
--      
		-- 1.3.6.1.4.1.9070.1.2.5.7.4.1.2.1
		enterWarmUpState NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 1 -- Entered warm-up state.
				
				It contains the OID and value for alarm ID, notify index, severity, transient, 
				date and time, severity, descriptions, and sequence number."
			::= { s650AlarmContain 1 }

		
--  
		-- 1.3.6.1.4.1.9070.1.2.5.7.4.1.2.2
		enterFreeRunState NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 2 -- Entered free-run state .
				
				It contains the OID and value for alarm ID, notify index, severity, transient, 
				date and time, severity, descriptions, and sequence number."
			::= { s650AlarmContain 2 }

		
		-- 1.3.6.1.4.1.9070.1.2.5.7.4.1.2.3
		enterFastTrackState NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 3 -- Entered fast-track state.
				
				It contains the OID and value for alarm ID, notify index, severity, transient, 
				date and time, severity, descriptions, and sequence number."
			::= { s650AlarmContain 3 }

		
		-- 1.3.6.1.4.1.9070.1.2.5.7.4.1.2.4
		enterNormalTrackState NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 4 -- Entered normal-track state.
				
				It contains the OID and value for alarm ID, notify index, severity, transient, 
				date and time, severity, descriptions, and sequence number."
			::= { s650AlarmContain 4 }

		
--  
		-- 1.3.6.1.4.1.9070.1.2.5.7.4.1.2.5
		enterBridgeState NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 5 -- Entered bridge state.
				
				It contains the OID and value for alarm ID, notify index, severity, transient, 
				date and time, severity, descriptions, and sequence number ."
			::= { s650AlarmContain 5 }

		
		-- 1.3.6.1.4.1.9070.1.2.5.7.4.1.2.6
		enterHoldoverState NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 6-- Entered holdover state.
				
				It contains the OID and value for alarm ID, notify index, severity, transient, 
				date and time, severity, descriptions, and sequence number." 
			::= { s650AlarmContain 6 }

		
--  
		
		-- 1.3.6.1.4.1.9070.1.2.5.7.4.1.2.8
		enterHoldoverRecoveryState NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 8 -- Entered holdover recovery state.
				
				It contains the OID and value for alarm ID, notify index, severity, transient, 
				date and time, severity, descriptions, and sequence number." 
			::= { s650AlarmContain 8 }

--  
		
		-- 1.3.6.1.4.1.9070.1.2.5.7.4.1.2.9
		powerUpFirstNormalTrack NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 8 -- First Normal-track since powerup
				
				It contains the OID and value for alarm ID, notify index, severity, transient, 
				date and time, severity, descriptions, and sequence number." 
			::= { s650AlarmContain 9 }

--
		-- 1.3.6.1.4.1.9070.1.2.5.7.4.1.2.21
		inputRefPoorQuality NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 21 -- Input reference poor quality.
				
				It contains the OID and value for alarm ID, notify index, severity, transient, 
				date and time, severity, descriptions, and sequence number." 
			::= { s650AlarmContain 21 }

--
		-- 1.3.6.1.4.1.9070.1.2.5.7.4.1.2.22
		channelTimeQualified NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 22 -- Channel Time Qualified.
				This event is reserved and presently not used.
				
				It contains the OID and value for alarm ID, notify index, severity, transient, 
				date and time, severity, descriptions, and sequence number." 
			::= { s650AlarmContain 22 }

--
		-- 1.3.6.1.4.1.9070.1.2.5.7.4.1.2.23
		channelFreqQualified NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 23 -- Channel Frequency Qualifed.
				This event is reserved and presently not used.
				
				It contains the OID and value for alarm ID, notify index, severity, transient, 
				date and time, severity, descriptions, and sequence number." 
			::= { s650AlarmContain 23 }

--   
		-- 1.3.6.1.4.1.9070.1.2.5.7.4.1.2.24
		inputSelectAsTimeRef NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 24 -- Input selected as time refereence.
				
				It contains the OID and value for alarm ID, notify index, severity, transient, 
				date and time, severity, descriptions, and sequence number." 
			::= { s650AlarmContain 24 }

--  
		-- 1.3.6.1.4.1.9070.1.2.5.7.4.1.2.25
		inputSelectAsFreqRef NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 25 -- Input selected as frequency reference.
				
				It contains the OID and value for alarm ID, notify index, severity, transient, 
				date and time, severity, descriptions, and sequence number." 
			::= { s650AlarmContain 25 }

--  
		-- 1.3.6.1.4.1.9070.1.2.5.7.4.1.2.27
		inputAIS NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 27 -- Input Alarm Indication Signal (AIS).
				
				It contains the OID and value for alarm ID, notify index, severity, transient, 
				date and time, severity, descriptions, and sequence number." 
			::= { s650AlarmContain 27 }
--  
		-- 1.3.6.1.4.1.9070.1.2.5.7.4.1.2.28
		inputOOF NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 28 -- Input Out of Frame (OOF).
				
				It contains the OID and value for alarm ID, notify index, severity, transient, 
				date and time, severity, descriptions, and sequence number." 
			::= { s650AlarmContain 28 }

--  
		-- 1.3.6.1.4.1.9070.1.2.5.7.4.1.2.29
		inputCRCError NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 29 -- Input CRC Error.
				
				It contains the OID and value for alarm ID, notify index, severity, transient, 
				date and time, severity, descriptions, and sequence number." 
			::= { s650AlarmContain 29 }
            --  
		-- 1.3.6.1.4.1.9070.1.2.5.7.4.1.2.30
		inputBPV NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 30 -- Input Bipolar Violation (BPV).
				
				It contains the OID and value for alarm ID, notify index, severity, transient, 
				date and time, severity, descriptions, and sequence number." 
			::= { s650AlarmContain 30 }
--  
		-- 1.3.6.1.4.1.9070.1.2.5.7.4.1.2.31
		inputFrequencyError NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 31 -- Input Frequency Error.
				This event is reserved and presently not used.
				
				It contains the OID and value for alarm ID, notify index, severity, transient, 
				date and time, severity, descriptions, and sequence number." 
			::= { s650AlarmContain 31 }
--  
		-- 1.3.6.1.4.1.9070.1.2.5.7.4.1.2.32
		inputSSMChanged NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 32 -- Input SSM Changed.
				This event is reserved and presently not used.
				
				It contains the OID and value for alarm ID, notify index, severity, transient, 
				date and time, severity, descriptions, and sequence number." 
			::= { s650AlarmContain 32 }
--  
		-- 1.3.6.1.4.1.9070.1.2.5.7.4.1.2.33 
		gnssTimeQualified NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 33 -- GNSS Time Qualified.
				
				It contains the OID and value for alarm ID, notify index, severity, transient, 
				date and time, severity, descriptions, and sequence number." 
			::= { s650AlarmContain 33 }
--  
		-- 1.3.6.1.4.1.9070.1.2.5.7.4.1.2.34
		ntpTimeQualified NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 34 -- NTP Time Qualified.
				
				It contains the OID and value for alarm ID, notify index, severity, transient, 
				date and time, severity, descriptions, and sequence number." 
			::= { s650AlarmContain 34 }

--  
		-- 1.3.6.1.4.1.9070.1.2.5.7.4.1.2.35
		ptpTimeQualified NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 35 -- PTP Time Qualified.
				
				It contains the OID and value for alarm ID, notify index, severity, transient, 
				date and time, severity, descriptions, and sequence number." 
			::= { s650AlarmContain 35 }

--  
		-- 1.3.6.1.4.1.9070.1.2.5.7.4.1.2.36
		j1ATimeQualified NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 36 -- J1A Time Qualified.
				
				It contains the OID and value for alarm ID, notify index, severity, transient, 
				date and time, severity, descriptions, and sequence number." 
			::= { s650AlarmContain 36 }

--  
		-- 1.3.6.1.4.1.9070.1.2.5.7.4.1.2.37
		j1BTimeQualified NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 37 -- J1B Time Qualified.
				
				It contains the OID and value for alarm ID, notify index, severity, transient, 
				date and time, severity, descriptions, and sequence number." 
			::= { s650AlarmContain 37 }

--  
		-- 1.3.6.1.4.1.9070.1.2.5.7.4.1.2.40
		gnssFrequencyQualified NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 40 -- GNSS Frequency Qualified.
				
				It contains the OID and value for alarm ID, notify index, severity, transient, 
				date and time, severity, descriptions, and sequence number." 
			::= { s650AlarmContain 40 }
--  
		-- 1.3.6.1.4.1.9070.1.2.5.7.4.1.2.41
		ntpFrequencyQualified NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 41 -- NTP Frequency Qualified.
				This event is reserved and presently not used.
				
				It contains the OID and value for alarm ID, notify index, severity, transient, 
				date and time, severity, descriptions, and sequence number." 
			::= { s650AlarmContain 41 }

--  
		-- 1.3.6.1.4.1.9070.1.2.5.7.4.1.2.42
		ptpFrequencyQualified NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 42 -- PTP Frequency Qualified.
				
				It contains the OID and value for alarm ID, notify index, severity, transient, 
				date and time, severity, descriptions, and sequence number." 
			::= { s650AlarmContain 42 }

--  
		-- 1.3.6.1.4.1.9070.1.2.5.7.4.1.2.43
		j1AFrequencyQualified NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 43 -- J1A Frequency Qualified.
				
				It contains the OID and value for alarm ID, notify index, severity, transient, 
				date and time, severity, descriptions, and sequence number." 
			::= { s650AlarmContain 43 }
--  
		-- 1.3.6.1.4.1.9070.1.2.5.7.4.1.2.44
		j1BFrequencyQualified NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 44 -- J1B Frequency Qualified.
				
				It contains the OID and value for alarm ID, notify index, severity, transient, 
				date and time, severity, descriptions, and sequence number." 
			::= { s650AlarmContain 44 }

--  
		-- 1.3.6.1.4.1.9070.1.2.5.7.4.1.2.45
		j2AFrequencyQualified NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 45 -- J2A Frequency Qualified.
				
				It contains the OID and value for alarm ID, notify index, severity, transient, 
				date and time, severity, descriptions, and sequence number." 
			::= { s650AlarmContain 45 }
--  
		-- 1.3.6.1.4.1.9070.1.2.5.7.4.1.2.46
		j2BFrequencyQualified NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 46 -- J2B Frequency Qualified.
				
				It contains the OID and value for alarm ID, notify index, severity, transient, 
				date and time, severity, descriptions, and sequence number." 
			::= { s650AlarmContain 46 }

--
            	-- 1.3.6.1.4.1.9070.1.2.5.7.4.1.2.47
		j7AFrequencyQualified NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 47 -- J7A Frequency Qualified.
				
				It contains the OID and value for alarm ID, notify index, severity, transient, 
				date and time, severity, descriptions, and sequence number." 
			::= { s650AlarmContain 47 }

--
	          -- 1.3.6.1.4.1.9070.1.2.5.7.4.1.2.48
		j7BFrequencyQualified NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 48 -- J7B Frequency Qualified.
				
				It contains the OID and value for alarm ID, notify index, severity, transient, 
				date and time, severity, descriptions, and sequence number." 
			::= { s650AlarmContain 48 }


--  
		-- 1.3.6.1.4.1.9070.1.2.5.7.4.1.2.51
		incompatibleTransport NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 51 -- Incompatible Transport.
				
				It contains the OID and value for alarm ID, notify index, severity, transient, 
				date and time, severity, descriptions, and sequence number." 
			::= { s650AlarmContain 51 }
--  
		-- 1.3.6.1.4.1.9070.1.2.5.7.4.1.2.52
		ptpInputChange NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 52 -- PTP Input Change.
				
				It contains the OID and value for alarm ID, notify index, severity, transient, 
				date and time, severity, descriptions, and sequence number." 
			::= { s650AlarmContain 52 }
		
--  
		-- 1.3.6.1.4.1.9070.1.2.5.7.4.1.2.53
		ptpMasterSwitched NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 53 -- PTP Master Switched.
				
				It contains the OID and value for alarm ID, notify index, severity, transient, 
				date and time, severity, descriptions, and sequence number." 
			::= { s650AlarmContain 53 }
		
--  
		-- 1.3.6.1.4.1.9070.1.2.5.7.4.1.2.54
		ptpInputNotTraceable NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 54 -- PTP Input Not Traceable.
				
				It contains the OID and value for alarm ID, notify index, severity, transient, 
				date and time, severity, descriptions, and sequence number." 
			::= { s650AlarmContain 54 }
--
		-- 1.3.6.1.4.1.9070.1.2.5.7.4.1.2.71
		ptpClientLimit NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 71 -- PTP Client Limit.
				This event is reserved and presently not used.
				
				It contains the OID and value for alarm ID, notify index, severity, transient, 
				date and time, severity, descriptions, and sequence number." 
			::= { s650AlarmContain 71 }

--
		-- 1.3.6.1.4.1.9070.1.2.5.7.4.1.2.72
		ptpClientDrop NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 72 -- PTP Client Drop.
				
				It contains the OID and value for alarm ID, notify index, severity, transient, 
				date and time, severity, descriptions, and sequence number." 
			::= { s650AlarmContain 72 }

--
		-- 1.3.6.1.4.1.9070.1.2.5.7.4.1.2.73
		ptpClientAdd NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 73 -- PTP Client Add.
				
				It contains the OID and value for alarm ID, notify index, severity, transient, 
				date and time, severity, descriptions, and sequence number." 
			::= { s650AlarmContain 73 }

--
		-- 1.3.6.1.4.1.9070.1.2.5.7.4.1.2.74
		ptpClientListRefreshed NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 74 -- PTP Client List Refreshed.
				
				It contains the OID and value for alarm ID, notify index, severity, transient, 
				date and time, severity, descriptions, and sequence number." 
			::= { s650AlarmContain 74 }

--
		-- 1.3.6.1.4.1.9070.1.2.5.7.4.1.2.75
		ptpPortStateDisabled NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 75 -- PTP PortState Disabled
				
				It contains the OID and value for alarm ID, notify index, severity, transient, 
				date and time, severity, descriptions, and sequence number." 
			::= { s650AlarmContain 75 }

--
		-- 1.3.6.1.4.1.9070.1.2.5.7.4.1.2.76
		ptpPortStateListening NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 76 -- PTP PortState Listening
				
				It contains the OID and value for alarm ID, notify index, severity, transient, 
				date and time, severity, descriptions, and sequence number." 
			::= { s650AlarmContain 76 }

--
		-- 1.3.6.1.4.1.9070.1.2.5.7.4.1.2.77
		ptpPortStateMaster NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 77 -- PTP PortState Master
				
				It contains the OID and value for alarm ID, notify index, severity, transient, 
				date and time, severity, descriptions, and sequence number." 
			::= { s650AlarmContain 77 }

--
		-- 1.3.6.1.4.1.9070.1.2.5.7.4.1.2.78
		ptpPortStatePassive NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 78 -- PTP PortState Passive
				
				It contains the OID and value for alarm ID, notify index, severity, transient, 
				date and time, severity, descriptions, and sequence number." 
			::= { s650AlarmContain 78 }

--  
		-- 1.3.6.1.4.1.9070.1.2.5.7.4.1.2.91
		gnssReceiverCommFailed NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 91 -- GNSS receiver communication failed.
				
				It contains the OID and value for alarm ID, notify index, severity, transient, 
				date and time, severity, descriptions, and sequence number." 
			::= { s650AlarmContain 91 }

		
--  
		-- 1.3.6.1.4.1.9070.1.2.5.7.4.1.2.92
		gnssNotTracking NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 92 -- GNSS is not tracking.
				
				It contains the OID and value for alarm ID, notify index, severity, transient, 
				date and time, severity, descriptions, and sequence number." 
			::= { s650AlarmContain 92 }

--  
		-- 1.3.6.1.4.1.9070.1.2.5.7.4.1.2.93
		gnssSignalLow NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 93 -- GNSS Signal Low.
				
				It contains the OID and value for alarm ID, notify index, severity, transient, 
				date and time, severity, descriptions, and sequence number." 
			::= { s650AlarmContain 93 }

--  
		-- 1.3.6.1.4.1.9070.1.2.5.7.4.1.2.94
		gnssVoltageOutOfRange NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 94 -- GNSS Voltage out of range.
				This event is reserved and presently not used.
				
				It contains the OID and value for alarm ID, notify index, severity, transient, 
				date and time, severity, descriptions, and sequence number." 
			::= { s650AlarmContain 94 }

--  
		-- 1.3.6.1.4.1.9070.1.2.5.7.4.1.2.95
		gnssCurrentOutOfRange NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 95 -- GNSS Current out of Range.
				This event is reserved and presently not used.
				
				It contains the OID and value for alarm ID, notify index, severity, transient, 
				date and time, severity, descriptions, and sequence number." 
			::= { s650AlarmContain 95 }
		
--  
		-- 1.3.6.1.4.1.9070.1.2.5.7.4.1.2.96
		gnssAntCurrentShortCircuit NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 96 -- GNSS antenna current short circuuit
				
				It contains the OID and value for alarm ID, notify index, severity, transient, 
				date and time, severity, descriptions, and sequence number." 
			::= { s650AlarmContain 96 }

		
--  
		-- 1.3.6.1.4.1.9070.1.2.5.7.4.1.2.97
		gnssAntCurrentOpenCircuit NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 97 -- GNSS antenna current open circuit.
				
				It contains the OID and value for alarm ID, notify index, severity, transient, 
				date and time, severity, descriptions, and sequence number." 
			::= { s650AlarmContain 97 }

--  
		-- 1.3.6.1.4.1.9070.1.2.5.7.4.1.2.98
		gnssInputLOS NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 98 -- GNSS Input LOS.
				This event is reserved and presently not used.
				
				It contains the OID and value for alarm ID, notify index, severity, transient, 
				date and time, severity, descriptions, and sequence number." 
			::= { s650AlarmContain 98 }

--  
		-- 1.3.6.1.4.1.9070.1.2.5.7.4.1.2.99
		j1AInputLOS NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 99 -- J1A Input LOS.
				
				It contains the OID and value for alarm ID, notify index, severity, transient, 
				date and time, severity, descriptions, and sequence number." 
			::= { s650AlarmContain 99 }

--  
		-- 1.3.6.1.4.1.9070.1.2.5.7.4.1.2.100
		j1BInputLOS NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 100 -- J1B Input LOS.
				
				It contains the OID and value for alarm ID, notify index, severity, transient, 
				date and time, severity, descriptions, and sequence number." 
			::= { s650AlarmContain 100 }
--  
		-- 1.3.6.1.4.1.9070.1.2.5.7.4.1.2.101
		j2AInputLOS NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 101 -- J2A Input LOS
				
				It contains the OID and value for alarm ID, notify index, severity, transient, 
				date and time, severity, descriptions, and sequence number." 
			::= { s650AlarmContain 101 }
--  
		-- 1.3.6.1.4.1.9070.1.2.5.7.4.1.2.102
		j2BInputLOS NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 102 -- J2B Input LOS.
				
				It contains the OID and value for alarm ID, notify index, severity, transient, 
				date and time, severity, descriptions, and sequence number." 
			::= { s650AlarmContain 102 }

--  
		-- 1.3.6.1.4.1.9070.1.2.5.7.4.1.2.103
		j7AInputLOS NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 103 -- J7A Input LOS.
				
				It contains the OID and value for alarm ID, notify index, severity, transient, 
				date and time, severity, descriptions, and sequence number." 
			::= { s650AlarmContain 103 }

--  
		-- 1.3.6.1.4.1.9070.1.2.5.7.4.1.2.104
		j7BInputLOS NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 104 -- J7B Input LOS.
				
				It contains the OID and value for alarm ID, notify index, severity, transient, 
				date and time, severity, descriptions, and sequence number." 
			::= { s650AlarmContain 104 }

--	
		-- 1.3.6.1.4.1.9070.1.2.5.7.4.1.2.112
		excessiveTrafficOnEthPort NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 112 -- Excessive traffic on Ethernet port.
				
				It contains the OID and value for alarm ID, notify index, severity, transient, 
				date and time, severity, descriptions, and sequence number." 
			::= { s650AlarmContain 112 }

--  
		-- 1.3.6.1.4.1.9070.1.2.5.7.4.1.2.114
		syncEEthernetConfig NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 114 -- SYNCE Ethernet config.
				This event is reserved and presently not used.
				
				It contains the OID and value for alarm ID, notify index, severity, transient, 
				date and time, severity, descriptions, and sequence number." 
			::= { s650AlarmContain 114 }

--  
		-- 1.3.6.1.4.1.9070.1.2.5.7.4.1.2.115
		ethLAN1LinkDown NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 115 -- Ethernet LAN1 link down.
				
				It contains the OID and value for alarm ID, notify index, severity, transient, 
				date and time, severity, descriptions, and sequence number." 
			::= { s650AlarmContain 115 }

--  
		-- 1.3.6.1.4.1.9070.1.2.5.7.4.1.2.116
		ethLAN2LinkDown NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 116 -- Ethernet LAN2 link down.
				
				It contains the OID and value for alarm ID, notify index, severity, transient, 
				date and time, severity, descriptions, and sequence number." 
			::= { s650AlarmContain 116 }

--  
		-- 1.3.6.1.4.1.9070.1.2.5.7.4.1.2.117
		ethLAN3LinkDown NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 117 -- Ethernet LAN3 link down.
				
				It contains the OID and value for alarm ID, notify index, severity, transient, 
				date and time, severity, descriptions, and sequence number." 
			::= { s650AlarmContain 117 }

--  
		-- 1.3.6.1.4.1.9070.1.2.5.7.4.1.2.118
		ethLAN4LinkDown NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 118 -- Ethernet LAN4 link down.
				
				It contains the OID and value for alarm ID, notify index, severity, transient, 
				date and time, severity, descriptions, and sequence number." 
			::= { s650AlarmContain 118 }

--
		-- 1.3.6.1.4.1.9070.1.2.5.7.4.1.2.119
		ethLAN5LinkDown NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 119 -- Ethernet LAN5 link down.
				
				It contains the OID and value for alarm ID, notify index, severity, transient, 
				date and time, severity, descriptions, and sequence number." 
			::= { s650AlarmContain 119 }

--
		-- 1.3.6.1.4.1.9070.1.2.5.7.4.1.2.120
		ethLAN6LinkDown NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 120 -- Ethernet LAN6 link down.
				
				It contains the OID and value for alarm ID, notify index, severity, transient, 
				date and time, severity, descriptions, and sequence number." 
			::= { s650AlarmContain 120 }

--
		-- 1.3.6.1.4.1.9070.1.2.5.7.4.1.2.130
		serviceLoadLimitExceeded NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 130 -- service load limit exceeded.
				
				It contains the OID and value for alarm ID, notify index, severity, transient, 
				date and time, severity, descriptions, and sequence number." 
			::= { s650AlarmContain 130 }
--	
		-- 1.3.6.1.4.1.9070.1.2.5.7.4.1.2.131
		powerOutOfRange NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm 131 -- Power out of range.
				
				It contains the OID and value for alarm ID, notify index, severity, transient, 
				date and time, severity, descriptions, and sequence number." 
			::= { s650AlarmContain 131 }

		
--  
		-- 1.3.6.1.4.1.9070.1.2.5.7.4.1.2.132
		operationalFailure NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 132 -- Operational failure.
				
				It contains the OID and value for alarm ID, notify index, severity, transient, 
				date and time, severity, descriptions, and sequence number." 
			::= { s650AlarmContain 132 }

		
--  
		-- 1.3.6.1.4.1.9070.1.2.5.7.4.1.2.133
		batteryAFailure NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 133 -- battery A failure.
				This event is reserved and presently not used.
				
				It contains the OID and value for alarm ID, notify index, severity, transient, 
				date and time, severity, descriptions, and sequence number." 
			::= { s650AlarmContain 133 }

--  
		-- 1.3.6.1.4.1.9070.1.2.5.7.4.1.2.134
		batteryBFailure NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 134 -- battery B failure.
				This event is reserved and presently not used.
				
				It contains the OID and value for alarm ID, notify index, severity, transient, 
				date and time, severity, descriptions, and sequence number." 
			::= { s650AlarmContain 134 }

--  
		-- 1.3.6.1.4.1.9070.1.2.5.7.4.1.2.135
		systemFPGAFailure NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 135 -- FPGA failure.
				This event is reserved and presently not used.
				
				It contains the OID and value for alarm ID, notify index, severity, transient, 
				date and time, severity, descriptions, and sequence number." 
			::= { s650AlarmContain 135 }

--  
		-- 1.3.6.1.4.1.9070.1.2.5.7.4.1.2.136
		flashPartitionFailure NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 136 -- Flash Partition failure.
				This event is reserved and presently not used.
				
				It contains the OID and value for alarm ID, notify index, severity, transient, 
				date and time, severity, descriptions, and sequence number." 
			::= { s650AlarmContain 136 }

--  
		-- 1.3.6.1.4.1.9070.1.2.5.7.4.1.2.137
		synthUnlock NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 137 -- Synthesizer Unlock.
				
				It contains the OID and value for alarm ID, notify index, severity, transient, 
				date and time, severity, descriptions, and sequence number." 
			::= { s650AlarmContain 137 }

--
		-- 1.3.6.1.4.1.9070.1.2.5.7.4.1.2.138
		rubidiumPPLUnlock NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 138 -- Rubidium PPL unlock.
				
				It contains the OID and value for alarm ID, notify index, severity, transient, 
				date and time, severity, descriptions, and sequence number." 
			::= { s650AlarmContain 138 }
		
--
		-- 1.3.6.1.4.1.9070.1.2.5.7.4.1.2.139
		temperatureOutOfRange NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 139 -- Temperature out of range.
				
				It contains the OID and value for alarm ID, notify index, severity, transient, 
				date and time, severity, descriptions, and sequence number." 
			::= { s650AlarmContain 139 }

--
		-- 1.3.6.1.4.1.9070.1.2.5.7.4.1.2.140
		fanFailure NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 140 -- Fan Failure.
				
				It contains the OID and value for alarm ID, notify index, severity, transient, 
				date and time, severity, descriptions, and sequence number." 
			::= { s650AlarmContain 140 }

--
		-- 1.3.6.1.4.1.9070.1.2.5.7.4.1.2.151
		productionConfigDataError NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 151-- production configuration data error.
				This event is reserved and presently not used.
				
				It contains the OID and value for alarm ID, notify index, severity, transient, 
				date and time, severity, descriptions, and sequence number." 
			::= { s650AlarmContain 151 }

--   
		-- 1.3.6.1.4.1.9070.1.2.5.7.4.1.2.152
		timeLineChanged NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 152 -- Time line has been changed.
				
				It contains the OID and value for alarm ID, notify index, severity, transient, 
				date and time, severity, descriptions, and sequence number." 
			::= { s650AlarmContain 152 }

		
--  
		-- 1.3.6.1.4.1.9070.1.2.5.7.4.1.2.153
		phaseChanged NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 153 -- Phase has been changed.
				
				It contains the OID and value for alarm ID, notify index, severity, transient, 
				date and time, severity, descriptions, and sequence number." 
			::= { s650AlarmContain 153 }

		
--   
		-- 1.3.6.1.4.1.9070.1.2.5.7.4.1.2.154
		sysLogTimeUpdate NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 154 -- system log time updated.
				This event is reserved and presently not used.
				
				It contains the OID and value for alarm ID, notify index, severity, transient, 
				date and time, severity, descriptions, and sequence number." 
			::= { s650AlarmContain 154 }

--	
		-- 1.3.6.1.4.1.9070.1.2.5.7.4.1.2.155
		s650SystemReboot NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 155 -- System reboot
				
				It contains the OID and value for alarm ID, notify index, severity, transient, 
				date and time, severity, descriptions, and sequence number." 
			::= { s650AlarmContain 155 }

--	
		-- 1.3.6.1.4.1.9070.1.2.5.7.4.1.2.157
		timeQL1eM6 NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 156 -- time QL1eM6
				
				It contains the OID and value for alarm ID, notify index, severity, transient, 
				date and time, severity, descriptions, and sequence number." 
			::= { s650AlarmContain 157 }

--	
		-- 1.3.6.1.4.1.9070.1.2.5.7.4.1.2.158
		timeQL1eM5 NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 158 -- Time QL1eM5
				
				It contains the OID and value for alarm ID, notify index, severity, transient, 
				date and time, severity, descriptions, and sequence number." 
			::= { s650AlarmContain 158 }
--	
		-- 1.3.6.1.4.1.9070.1.2.5.7.4.1.2.159
		timeQL1eM4 NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 159 -- Time QL1eM5
				
				It contains the OID and value for alarm ID, notify index, severity, transient, 
				date and time, severity, descriptions, and sequence number." 
			::= { s650AlarmContain 159 }
--	
		-- 1.3.6.1.4.1.9070.1.2.5.7.4.1.2.160
		timeQL1eM3 NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 160 -- Time QL1eM5
				
				It contains the OID and value for alarm ID, notify index, severity, transient, 
				date and time, severity, descriptions, and sequence number." 
			::= { s650AlarmContain 160 }
--	
		-- 1.3.6.1.4.1.9070.1.2.5.7.4.1.2.161
		ntpSysPeerChanged NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 161 -- NTP system peer change
				
				It contains the OID and value for alarm ID, notify index, severity, transient, 
				date and time, severity, descriptions, and sequence number." 
			::= { s650AlarmContain 161 }

--	
		-- 1.3.6.1.4.1.9070.1.2.5.7.4.1.2.162
		ntpStratumChanged NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 162 -- NTP Stratum Changed
				
				It contains the OID and value for alarm ID, notify index, severity, transient, 
				date and time, severity, descriptions, and sequence number." 
			::= { s650AlarmContain 162 }
--	
		-- 1.3.6.1.4.1.9070.1.2.5.7.4.1.2.163
		ntpLeapChange NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 163 -- NTP Leap indicator Changed
				
				It contains the OID and value for alarm ID, notify index, severity, transient, 
				date and time, severity, descriptions, and sequence number." 
			::= { s650AlarmContain 163 }
--	
		-- 1.3.6.1.4.1.9070.1.2.5.7.4.1.2.164
		sysUpgradeAvailable NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 164 -- System upgrade available
				
				It contains the OID and value for alarm ID, notify index, severity, transient, 
				date and time, severity, descriptions, and sequence number." 
			::= { s650AlarmContain 164 }
--	
		-- 1.3.6.1.4.1.9070.1.2.5.7.4.1.2.170
	    j1AIrigInputFault NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 170 -- J1A IRIG Input fault
				
				It contains the OID and value for alarm ID, notify index, severity, transient, 
				date and time, severity, descriptions, and sequence number." 
			::= { s650AlarmContain 170 }

-- 
    	-- 1.3.6.1.4.1.9070.1.2.5.7.4.1.2.171
		j1BIrigInputFault NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 171 -- J1B IRIG input protocal fault
				
				It contains the OID and value for alarm ID, notify index, severity, transient, 
				date and time, severity, descriptions, and sequence number." 
			::= { s650AlarmContain 171 }

-- 
    	-- 1.3.6.1.4.1.9070.1.2.5.7.4.1.2.172
		holdoverTimeExceed NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 172 -- Holdover Time Error Estimate Exceed
				
				It contains the OID and value for alarm ID, notify index, severity, transient, 
				date and time, severity, descriptions, and sequence number." 
			::= { s650AlarmContain 172 }


-- 
    	-- 1.3.6.1.4.1.9070.1.2.5.7.4.1.2.173
		leapPending NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 173 -- Leap Event Pending
				
				It contains the OID and value for alarm ID, notify index, severity, transient, 
				date and time, severity, descriptions, and sequence number." 
				
			::= { s650AlarmContain 173 }

-- 
    	-- 1.3.6.1.4.1.9070.1.2.5.7.4.1.2.174
		excessiveFreqAdjust NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 174 -- Excessive Frequency Adjust
				
				It contains the OID and value for alarm ID, notify index, severity, transient, 
				date and time, severity, descriptions, and sequence number." 
			::= { s650AlarmContain 174 }

-- 
    	-- 1.3.6.1.4.1.9070.1.2.5.7.4.1.2.175
		acPowerNotPresent NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 175 -- Power Not Present
				0=AC1, 1=AC2, 2=DC1, 3=DC2
				
				It contains the OID and value for alarm ID, notify index, severity, transient, 
				date and time, severity, descriptions, and sequence number." 
			::= { s650AlarmContain 175 }

-- 
    	-- 1.3.6.1.4.1.9070.1.2.5.7.4.1.2.176
		fullSysConfig NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 176 -- Full system Configuration occured
				
				It contains the OID and value for alarm ID, notify index, severity, transient, 
				date and time, severity, descriptions, and sequence number." 
			::= { s650AlarmContain 176 }

-- 
    	-- 1.3.6.1.4.1.9070.1.2.5.7.4.1.2.177
		configChange NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 177 -- Configuration change
				
				It contains the OID and value for alarm ID, notify index, severity, transient, 
				date and time, severity, descriptions, and sequence number." 
			::= { s650AlarmContain 177 }
--

    	-- 1.3.6.1.4.1.9070.1.2.5.7.4.1.2.178
		loginActivity NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 178 -- login activity
				This event is reserved and presently not used.
				
				It contains the OID and value for alarm ID, notify index, severity, transient, 
				date and time, severity, descriptions, and sequence number." 
			::= { s650AlarmContain 178 }
--  

    	-- 1.3.6.1.4.1.9070.1.2.5.7.4.1.2.179
		lpnOscillatorUnlock NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 179 -- LPN Oscillator Unlock
				
				It contains the OID and value for alarm ID, notify index, severity, transient, 
				date and time, severity, descriptions, and sequence number." 
			::= { s650AlarmContain 179 }

--
    	-- 1.3.6.1.4.1.9070.1.2.5.7.4.1.2.180
		manualTimeEntryModeEnabled NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 180 -- manual TimeEntry Mode Enabled
				
				It contains the OID and value for alarm ID, notify index, severity, transient, 
				date and time, severity, descriptions, and sequence number." 
			::= { s650AlarmContain 180 }
--            

    	-- 1.3.6.1.4.1.9070.1.2.5.7.4.1.2.181
		lpnOscillatorStateChange NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 181 -- LPN Oscillator State Change
				
				It contains the OID and value for alarm ID, notify index, severity, transient, 
				date and time, severity, descriptions, and sequence number." 
			::= { s650AlarmContain 181 }

--
    	-- 1.3.6.1.4.1.9070.1.2.5.7.4.1.2.182
		ntpReflectorStatePassive NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 182 -- NTP Reflector State Change Passive
				
				It contains the OID and value for alarm ID, notify index, severity, transient, 
				date and time, severity, descriptions, and sequence number." 
			::= { s650AlarmContain 182 }

--
    	-- 1.3.6.1.4.1.9070.1.2.5.7.4.1.2.183
		ntpReflectorStateServer NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 183 -- NTP Reflector State Change Server
				
				It contains the OID and value for alarm ID, notify index, severity, transient, 
				date and time, severity, descriptions, and sequence number." 
			::= { s650AlarmContain 183 }

--
    	-- 1.3.6.1.4.1.9070.1.2.5.7.4.1.2.184
		eventOverflow NOTIFICATION-TYPE
			OBJECTS { s650NotifyAlarmEventID, s650NotifyAlarmAction, s650NotifyIndex, s650NotifySeverity, s650NotifyDateTime, 
				s650NotifyDescription, s650NotifySequenceNum }
			STATUS current
			DESCRIPTION 
				"Alarm/Event 183 -- Event Overflow
				
				It contains the OID and value for alarm ID, notify index, severity, transient, 
				date and time, severity, descriptions, and sequence number." 
			::= { s650AlarmContain 184 }


--
		-- 1.3.6.1.4.1.9070.1.2.5.7.4.2
		s650AlarmConformance OBJECT-IDENTITY
			STATUS current
			DESCRIPTION 
				"This subtree contains conformance statements for the
				SyncServer S650 alarm MIB module.
				"
			::= { s650Alarm 2 }

		
--  
		-- 1.3.6.1.4.1.9070.1.2.5.7.4.2.1
		s650AlarmCompliances OBJECT IDENTIFIER ::= { s650AlarmConformance 1 }


        -- 1.3.6.1.4.1.9070.1.2.5.7.4.2.1.1
		s650BasicCompliance MODULE-COMPLIANCE
			STATUS current
			DESCRIPTION 
				"Basic compliance"
			MODULE -- this module
				MANDATORY-GROUPS { s650NotifyGroup, s650AlarmGroup }
			::= { s650AlarmCompliances 1 }


		
		-- 1.3.6.1.4.1.9070.1.2.5.7.4.2.2
		s650AlarmUocGroups OBJECT IDENTIFIER ::= { s650AlarmConformance 2 }
        
        	-- 1.3.6.1.4.1.9070.1.2.5.7.6.3.2.1
		s650NotifyGroup OBJECT-GROUP
			OBJECTS { s650NotifyAlarmEventID, s650NotifyIndex, s650NotifySeverity, s650NotifyDateTime, s650NotifyDescription, 
				s650NotifySequenceNum, s650NotifyClientClockID, s650NotifyAlarmAction, s650NotifyTransient, s650NotifyClientAddr
				 }
			STATUS current
			DESCRIPTION 
				"Notify elements of S50ALARM.mib"
			::= { s650AlarmUocGroups 1 }

		
		-- 1.3.6.1.4.1.9070.1.2.5.7.6.3.2.2
		s650AlarmGroup NOTIFICATION-GROUP
			NOTIFICATIONS { enterWarmUpState, enterFreeRunState, enterFastTrackState, enterNormalTrackState, enterBridgeState, 
				enterHoldoverState, enterHoldoverRecoveryState, powerUpFirstNormalTrack, inputRefPoorQuality, channelTimeQualified, 
				channelFreqQualified, inputSelectAsTimeRef, inputSelectAsFreqRef, inputAIS, inputOOF, 
				inputCRCError, inputBPV, inputFrequencyError, inputSSMChanged, gnssTimeQualified, 
				ntpTimeQualified, ptpTimeQualified, j1ATimeQualified, j1BTimeQualified, gnssFrequencyQualified, 
				ntpFrequencyQualified, ptpFrequencyQualified, j1AFrequencyQualified, j1BFrequencyQualified, j2AFrequencyQualified, 
				j2BFrequencyQualified, incompatibleTransport, ptpInputChange, ptpMasterSwitched, ptpInputNotTraceable, 
				ptpClientLimit, ptpClientAdd, ptpClientDrop, ptpClientListRefreshed, ptpPortStateDisabled, 
				ptpPortStateListening, ptpPortStatePassive, gnssReceiverCommFailed, gnssNotTracking, gnssSignalLow, 
				gnssVoltageOutOfRange, gnssCurrentOutOfRange, gnssAntCurrentShortCircuit, gnssAntCurrentOpenCircuit, gnssInputLOS, 
				j1AInputLOS, j1BInputLOS, j2AInputLOS, j2BInputLOS, excessiveTrafficOnEthPort, 
				syncEEthernetConfig, ethLAN1LinkDown, ethLAN2LinkDown, ethLAN3LinkDown, ethLAN4LinkDown, 
				ethLAN5LinkDown, ethLAN6LinkDown, serviceLoadLimitExceeded, powerOutOfRange, ptpPortStateMaster, 
				operationalFailure, batteryAFailure, batteryBFailure, systemFPGAFailure, flashPartitionFailure, 
				synthUnlock, rubidiumPPLUnlock, temperatureOutOfRange, fanFailure, productionConfigDataError, 
				timeLineChanged, phaseChanged, sysLogTimeUpdate, s650SystemReboot, timeQL1eM6, 
				timeQL1eM5, timeQL1eM4, timeQL1eM3, ntpSysPeerChanged, ntpStratumChanged, 
				ntpLeapChange, sysUpgradeAvailable, j1AIrigInputFault, j1BIrigInputFault, holdoverTimeExceed, 
				leapPending, excessiveFreqAdjust, acPowerNotPresent, fullSysConfig, configChange, 
				loginActivity, lpnOscillatorUnlock, manualTimeEntryModeEnabled, lpnOscillatorStateChange, ntpReflectorStatePassive, 
				ntpReflectorStateServer, j7AFrequencyQualified, j7BFrequencyQualified, j7AInputLOS, j7BInputLOS, eventOverflow}
			STATUS current
			DESCRIPTION 
				"Description."
			::= { s650AlarmUocGroups 2 }

		
	
	END

--
-- S650ALARM.my
--
