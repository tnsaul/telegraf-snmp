RBT-PRODUCT-MIB DEFINITIONS ::= BEGIN
IMPORTS
    DisplayString FROM RFC1213-MIB
    MODULE-IDENTITY, OBJECT-TYPE, Counter32, Gauge32, Counter64,
    Integer32, TimeTicks, mib-2, enterprises
    FROM SNMPv2-SMI
    rbt, productFamilies FROM RBT-MIB;

rbtProductsMib MODULE-IDENTITY
    LAST-UPDATED        "201806150000Z"
    ORGANIZATION        "Riverbed Technology, Inc."
    CONTACT-INFO
    "   Riverbed Technical Support
           support@riverbed.com"
    DESCRIPTION         "Riverbed Technology Products Definition MIB"

    REVISION 		"201708010000Z"
    DESCRIPTION         "Initial Revision"
    REVISION            "201806150000Z"
    DESCRIPTION         "Adding definition of a platform generic product"
    ::= { rbt 4 }

steelCentral OBJECT IDENTIFIER
    ::= { productFamilies 100}

scAppResponse OBJECT IDENTIFIER
    ::= { steelCentral 1}

scInsights OBJECT IDENTIFIER
    ::= { steelCentral 2}

scPlatform OBJECT IDENTIFIER
    ::= { steelCentral 3}

END
