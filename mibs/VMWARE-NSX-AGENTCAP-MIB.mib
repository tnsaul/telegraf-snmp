-- **********************************************************
-- Copyright 2020 VMware, Inc.  All rights reserved.
-- **********************************************************

VMWARE-NSX-AGENTCAP-MIB DEFINITIONS ::= BEGIN

IMPORTS
    MODULE-IDENTITY
       FROM SNMPv2-SMI
    vmwareAgentCapabilities
       FROM VMWARE-ROOT-MIB
    AGENT-CAPABILITIES
       FROM  SNMPv2-CONF;

vmwNSXAgentCapabilityMIB MODULE-IDENTITY
   LAST-UPDATED "202010300000Z"
   ORGANIZATION "VMware, Inc"
   CONTACT-INFO
      "VMware, Inc
      3401 Hillview Ave
      Palo Alto, CA 94304
      Tel: 1-877-486-9273 or 650-427-5000
      Fax: 650-427-5001
      Web: http://kb.vmware.com/kb/1013445
      "
   DESCRIPTION
     "This module defines agent capabilities for deployed VMware NSX agents by release."
   REVISION     "202104220000Z"
   DESCRIPTION
         "NSX-T Data Center 3.1.2 release. Supports both notifications and polling over v1/v2c/v3"
   REVISION     "202103250000Z"
   DESCRIPTION
         "NSX-T Data Center 3.0.3 release. Supports both notifications and polling over v1/v2c/v3"
   REVISION     "202010300000Z"
   DESCRIPTION
         "NSX-T Data Center 3.1.x releases. Supports both notifications and polling over v1/v2c/v3"
   REVISION     "202009220000Z"
   DESCRIPTION
         "NSX-T Data Center 3.0.2 release. Supports both notifications and polling over v1/v2c/v3"
   REVISION     "202003270000Z"
   DESCRIPTION
         "NSX-T Data Center 3.0.0 and 3.0.1 releases. Supports both notifications and polling over v1/v2c/v3"
        ::= { vmwareAgentCapabilities 26 }

vmwNSXCapability OBJECT IDENTIFIER ::= { vmwNSXAgentCapabilityMIB 1 }

--
-- Applies to NSX-T Data Center 3.0 Release and follow up patch releases
--

vmwNSXManagerDC30 AGENT-CAPABILITIES
  PRODUCT-RELEASE
     "VMware NSX-T Data Center 3.0"
  STATUS  current
  DESCRIPTION
     "Release 3.0 VMware NSX-T Data Center 3.0.
      Notifications may be v1, v2c, or v3 noAuthNoPriv to authPriv securityLevel with SHA1/AES128"
  REFERENCE  "http://www.vmware.com/products"

   -- NSX Specific Notifications
     SUPPORTS VMWARE-NSX-MIB
     INCLUDES {
         vmwNsxTDataCenterNotificationInfoGroup,
         vmwNsxTDataCenterNotificationInfoGroup2,
         vmwNsxTDataCenterNotificationInfoGroup3,
         vmwNsxTDataCenterNotificationInfoGroup6,
         vmwNsxTDataCenterNotificationGroup,
         vmwNsxTDataCenterNotificationGroup2,
         vmwNsxTDataCenterNotificationGroup3,
         vmwNsxTDataCenterNotificationGroup6
     }

   -- RFC 3418 sysObjectId in VMWARE-PRODUCTS-MIB node: vmwNSX
     SUPPORTS SNMPv2-MIB
     INCLUDES {
         snmpGroup,
         systemGroup,
         snmpCommunityGroup,
         snmpBasicNotificationsGroup,
         snmpWarmStartNotificationGroup
         -- groups not supported; snmpSetGroup, snmpNotificationGroup
     }
     VARIATION snmpSetSerialNo
     ACCESS  not-implemented
     DESCRIPTION "Agent provides read-only view of system information."

     VARIATION snmpTrapOID
     ACCESS not-implemented
     DESCRIPTION "Agent does not proxy other agents RFC1157 Trap-PDUs."

     VARIATION  snmpTrapEnterprise
     ACCESS not-implemented
     DESCRIPTION "Agent does not proxy other agents RFC1157 Trap-PDUs."

     VARIATION snmpEnableAuthenTraps
     SYNTAX INTEGER { disabled(2) }
     ACCESS read-only
     DESCRIPTION "Agent does not support authentication traps. Poll snmpInBadCommunityNames for same info."
     -- which implies:
     -- VARIATION authenticationFailure
     -- ACCESS not-implemented
     -- DESCRIPTION "Agent does not provide this notification. snmpEnableAuthenTraps will return disabled."

     -- ********************* ************ ************ *************** ***
     -- RFC 2863
     SUPPORTS IF-MIB
     INCLUDES {
         ifGeneralInformationGroup,
         linkUpDownNotificationsGroup
     }

     VARIATION ifAdminStatus
     ACCESS read-only
     DESCRIPTION "Agent provides read-only view of administrative state for each physical interface."

     VARIATION ifLinkUpDownTrapEnable
     ACCESS read-only
     DESCRIPTION "Agent provides read-only view of system information."

     VARIATION ifAlias
     ACCESS read-only
     DESCRIPTION "ifIndexes may only change across reboot."

     VARIATION ifInUnknownProtos
     ACCESS not-implemented
     DESCRIPTION "This counter always returns 0."

     -- ifRcvAddressGroup is interface/media specific
     VARIATION ifRcvAddressStatus
     ACCESS not-implemented
     DESCRIPTION "Required if media specific mib modules are implemented."

     VARIATION ifRcvAddressType
     ACCESS not-implemented
     DESCRIPTION "Required if media specific mib modules are implemented."

     -- ********************* ************ ************ *************** ***
     -- RFC 4293
     SUPPORTS IP-MIB
     INCLUDES {
         ipSystemStatsGroup,
         ipAddressGroup,
         ipNetToPhysicalGroup,
         ipDefaultRouterGroup,
         icmpStatsGroup,
         ipSystemStatsHCOctetGroup,
         ipSystemStatsHCPacketGroup,
         ipv4GeneralGroup,
         ipv4IfGroup,
         ipv4SystemStatsGroup,
         ipv4SystemStatsHCPacketGroup,
         ipv6GeneralGroup2,
         ipv6IfGroup,
         ipAddressPrefixGroup,
         ipv6RouterAdvertGroup,
         ipLastChangeGroup
     }
     -- VARIATION ipv6ScopeGroup
     -- ACCESS  not-implemented

     -- ********************* ************ ************ *************** ***
     -- RFC 4292
     -- supports SNMPv2/3 Contexts for multiple instances
     SUPPORTS IP-FORWARD-MIB
     INCLUDES {
         inetForwardCidrRouteGroup
     }

     -- RFC 4113
     -- supports SNMPv2/3 Contexts for multiple instances
     SUPPORTS UDP-MIB
     -- The next two 32 bit counters will be fixed per bug report PR 890894
     -- VARIATION udpInDatagrams
     -- ACCESS not-implemented, use udpHCInDatagrams
     -- VARIATION udpOutDatagrams
     -- ACCESS not-implemented, use udpHCOutDatagrams
     INCLUDES {
        udpBaseGroup,
        udpEndpointGroup
     }

     -- RFC 4022
     -- supports SNMPv2/3 Contexts for multiple instances
     SUPPORTS TCP-MIB
     INCLUDES {
         tcpBaseGroup,
         tcpConnectionGroup,
         tcpListenerGroup
     }

     -- RFC 2790
     -- NOTE: For storage larger than Integer32 (Terabyte) this agent will report INT_MAX
     SUPPORTS HOST-RESOURCES-MIB
     INCLUDES {
            hrSystemGroup,
            hrStorageGroup,
            hrDeviceGroup,
            hrSWRunGroup,
            hrSWRunPerfGroup,
            hrSWInstalledGroup  -- updates once an hour
     }

     VARIATION  hrSystemNumUsers
     ACCESS read-only
     DESCRIPTION "Value reports number of active appliace shell sessions"

     VARIATION  hrSystemDate
     ACCESS read-only
     DESCRIPTION "agent provides read only access"

     VARIATION hrSystemInitialLoadDevice
     ACCESS read-only
     DESCRIPTION "agent provides read only access"

     VARIATION hrSystemInitialLoadParameters
     ACCESS read-only
     DESCRIPTION "agent provides read only access"

     VARIATION hrStorageSize
     ACCESS read-only
     DESCRIPTION "agent provides read only access"

     VARIATION  hrSWRunStatus
     ACCESS read-only
     DESCRIPTION "agent provides read only access"

    -- hrDeviceStatus reports unknown for: cpu, nic either running/unknown.
    --               disk reports running, warning, down, unknown
    -- device error counters do not account for all failure cases

     VARIATION hrSWOSIndex
     ACCESS not-implemented
     DESCRIPTION "No operatingSystem entry exists in hrSWRunGroup hrSWRunTable"

     VARIATION  hrFSLastFullBackupDate
     ACCESS not-implemented
     DESCRIPTION "is not implemented"

     VARIATION  hrFSLastPartialBackupDate
     ACCESS not-implemented
     DESCRIPTION "is not implemented"

     VARIATION hrPrinterStatus
     ACCESS not-implemented
     DESCRIPTION "is not implemented"

     VARIATION hrPrinterDetectedErrorState
     ACCESS not-implemented
     DESCRIPTION "is not implemented"

     VARIATION hrSWInstalledTable
     ACCESS not-implemented
     DESCRIPTION "is not implemented"

     -- ********************* ************ ************ *************** ***
     -- RFC 4133
     -- SMBIOS data provided in entPhysicalTable
     SUPPORTS ENTITY-MIB
     INCLUDES {
        entityPhysicalGroup,
        entityPhysical2Group,
        entityPhysical3Group,
        entityGeneralGroup
     }
     -- VARIATION entityNotificationsGroup
     -- ACCESS not-implemented
     -- VARIATION entityMappingGroup
     -- ACCESS not-implemented

     -- ********************* ************ ************ *************** ***
     -- Enterprise MIB module to provide standardized product version information.
     -- REVISION 201008020000Z
     SUPPORTS VMWARE-SYSTEM-MIB
     INCLUDES {
         vmwSystemGroup
     }
     -- VARIATION vmwProdUpdate
     -- ACCESS not-implemented
     -- VARIATION vmwProdPatch
     -- ACCESS not-implemented

   ::= { vmwNSXCapability 11 }

--
-- Applies to NSX-T Data Center 3.1 Release and follow up patch releases
--

vmwNSXManagerDC30 AGENT-CAPABILITIES
  PRODUCT-RELEASE
     "VMware NSX-T Data Center 3.1"
  STATUS  current
  DESCRIPTION
     "Release 3.1 VMware NSX-T Data Center 3.1.
      Notifications may be v1, v2c, or v3 noAuthNoPriv to authPriv securityLevel with SHA1/AES128"
  REFERENCE  "http://www.vmware.com/products"

   -- NSX Specific Notifications
     SUPPORTS VMWARE-NSX-MIB
     INCLUDES {
         vmwNsxTDataCenterNotificationInfoGroup,
         vmwNsxTDataCenterNotificationInfoGroup2,
         vmwNsxTDataCenterNotificationInfoGroup3,
         vmwNsxTDataCenterNotificationInfoGroup4,
         vmwNsxTDataCenterNotificationInfoGroup6,
         vmwNsxTDataCenterNotificationInfoGroup7,
         vmwNsxTDataCenterNotificationGroup,
         vmwNsxTDataCenterNotificationGroup2,
         vmwNsxTDataCenterNotificationGroup3,
         vmwNsxTDataCenterNotificationGroup4,
         vmwNsxTDataCenterNotificationGroup5,
         vmwNsxTDataCenterNotificationGroup6,
         vmwNsxTDataCenterNotificationGroup7
     }

   -- RFC 3418 sysObjectId in VMWARE-PRODUCTS-MIB node: vmwNSX
     SUPPORTS SNMPv2-MIB
     INCLUDES {
         snmpGroup,
         systemGroup,
         snmpCommunityGroup,
         snmpBasicNotificationsGroup,
         snmpWarmStartNotificationGroup
         -- groups not supported; snmpSetGroup, snmpNotificationGroup
     }
     VARIATION snmpSetSerialNo
     ACCESS  not-implemented
     DESCRIPTION "Agent provides read-only view of system information."

     VARIATION snmpTrapOID
     ACCESS not-implemented
     DESCRIPTION "Agent does not proxy other agents RFC1157 Trap-PDUs."

     VARIATION  snmpTrapEnterprise
     ACCESS not-implemented
     DESCRIPTION "Agent does not proxy other agents RFC1157 Trap-PDUs."

     VARIATION snmpEnableAuthenTraps
     SYNTAX INTEGER { disabled(2) }
     ACCESS read-only
     DESCRIPTION "Agent does not support authentication traps. Poll snmpInBadCommunityNames for same info."
     -- which implies:
     -- VARIATION authenticationFailure
     -- ACCESS not-implemented
     -- DESCRIPTION "Agent does not provide this notification. snmpEnableAuthenTraps will return disabled."

     -- ********************* ************ ************ *************** ***
     -- RFC 2863
     SUPPORTS IF-MIB
     INCLUDES {
         ifGeneralInformationGroup,
         linkUpDownNotificationsGroup
     }

     VARIATION ifAdminStatus
     ACCESS read-only
     DESCRIPTION "Agent provides read-only view of administrative state for each physical interface."

     VARIATION ifLinkUpDownTrapEnable
     ACCESS read-only
     DESCRIPTION "Agent provides read-only view of system information."

     VARIATION ifAlias
     ACCESS read-only
     DESCRIPTION "ifIndexes may only change across reboot."

     VARIATION ifInUnknownProtos
     ACCESS not-implemented
     DESCRIPTION "This counter always returns 0."

     -- ifRcvAddressGroup is interface/media specific
     VARIATION ifRcvAddressStatus
     ACCESS not-implemented
     DESCRIPTION "Required if media specific mib modules are implemented."

     VARIATION ifRcvAddressType
     ACCESS not-implemented
     DESCRIPTION "Required if media specific mib modules are implemented."

     -- ********************* ************ ************ *************** ***
     -- RFC 4293
     SUPPORTS IP-MIB
     INCLUDES {
         ipSystemStatsGroup,
         ipAddressGroup,
         ipNetToPhysicalGroup,
         ipDefaultRouterGroup,
         icmpStatsGroup,
         ipSystemStatsHCOctetGroup,
         ipSystemStatsHCPacketGroup,
         ipv4GeneralGroup,
         ipv4IfGroup,
         ipv4SystemStatsGroup,
         ipv4SystemStatsHCPacketGroup,
         ipv6GeneralGroup2,
         ipv6IfGroup,
         ipAddressPrefixGroup,
         ipv6RouterAdvertGroup,
         ipLastChangeGroup
     }
     -- VARIATION ipv6ScopeGroup
     -- ACCESS  not-implemented

     -- ********************* ************ ************ *************** ***
     -- RFC 4292
     -- supports SNMPv2/3 Contexts for multiple instances
     SUPPORTS IP-FORWARD-MIB
     INCLUDES {
         inetForwardCidrRouteGroup
     }

     -- RFC 4113
     -- supports SNMPv2/3 Contexts for multiple instances
     SUPPORTS UDP-MIB
     -- The next two 32 bit counters will be fixed per bug report PR 890894
     -- VARIATION udpInDatagrams
     -- ACCESS not-implemented, use udpHCInDatagrams
     -- VARIATION udpOutDatagrams
     -- ACCESS not-implemented, use udpHCOutDatagrams
     INCLUDES {
        udpBaseGroup,
        udpEndpointGroup
     }

     -- RFC 4022
     -- supports SNMPv2/3 Contexts for multiple instances
     SUPPORTS TCP-MIB
     INCLUDES {
         tcpBaseGroup,
         tcpConnectionGroup,
         tcpListenerGroup
     }

     -- RFC 2790
     -- NOTE: For storage larger than Integer32 (Terabyte) this agent will report INT_MAX
     SUPPORTS HOST-RESOURCES-MIB
     INCLUDES {
            hrSystemGroup,
            hrStorageGroup,
            hrDeviceGroup,
            hrSWRunGroup,
            hrSWRunPerfGroup,
            hrSWInstalledGroup  -- updates once an hour
     }

     VARIATION  hrSystemNumUsers
     ACCESS read-only
     DESCRIPTION "Value reports number of active appliace shell sessions"

     VARIATION  hrSystemDate
     ACCESS read-only
     DESCRIPTION "agent provides read only access"

     VARIATION hrSystemInitialLoadDevice
     ACCESS read-only
     DESCRIPTION "agent provides read only access"

     VARIATION hrSystemInitialLoadParameters
     ACCESS read-only
     DESCRIPTION "agent provides read only access"

     VARIATION hrStorageSize
     ACCESS read-only
     DESCRIPTION "agent provides read only access"

     VARIATION  hrSWRunStatus
     ACCESS read-only
     DESCRIPTION "agent provides read only access"

    -- hrDeviceStatus reports unknown for: cpu, nic either running/unknown.
    --               disk reports running, warning, down, unknown
    -- device error counters do not account for all failure cases

     VARIATION hrSWOSIndex
     ACCESS not-implemented
     DESCRIPTION "No operatingSystem entry exists in hrSWRunGroup hrSWRunTable"

     VARIATION  hrFSLastFullBackupDate
     ACCESS not-implemented
     DESCRIPTION "is not implemented"

     VARIATION  hrFSLastPartialBackupDate
     ACCESS not-implemented
     DESCRIPTION "is not implemented"

     VARIATION hrPrinterStatus
     ACCESS not-implemented
     DESCRIPTION "is not implemented"

     VARIATION hrPrinterDetectedErrorState
     ACCESS not-implemented
     DESCRIPTION "is not implemented"

     VARIATION hrSWInstalledTable
     ACCESS not-implemented
     DESCRIPTION "is not implemented"

     -- ********************* ************ ************ *************** ***
     -- RFC 4133
     -- SMBIOS data provided in entPhysicalTable
     SUPPORTS ENTITY-MIB
     INCLUDES {
        entityPhysicalGroup,
        entityPhysical2Group,
        entityPhysical3Group,
        entityGeneralGroup
     }
     -- VARIATION entityNotificationsGroup
     -- ACCESS not-implemented
     -- VARIATION entityMappingGroup
     -- ACCESS not-implemented

     -- ********************* ************ ************ *************** ***
     -- Enterprise MIB module to provide standardized product version information.
     -- REVISION 201008020000Z
     SUPPORTS VMWARE-SYSTEM-MIB
     INCLUDES {
         vmwSystemGroup
     }
     -- VARIATION vmwProdUpdate
     -- ACCESS not-implemented
     -- VARIATION vmwProdPatch
     -- ACCESS not-implemented

   ::= { vmwNSXCapability 13 }

END
